[DOCUMENT]
TITLE: System Requirements

[GRAMMAR]
IMPORT_FROM_FILE: grammar.sgra

[SYS_REQUIREMENT]
UID: SYS-001
TITLE: ARM Cortex-A8 Zielplattform
STATEMENT: Das System muss auf einem BeagleBone Black mit ARM Cortex-A8 Prozessor und 512 MB RAM lauffähig sein.
STATUS: Active
RELATIONS:
- TYPE: File
  VALUE: project/go-api/cmd/main.go

[SYS_REQUIREMENT]
UID: SYS-002
TITLE: Betriebssystem
STATEMENT: Das System muss unter Linux (Debian) auf dem BeagleBone Black betrieben werden können.
STATUS: Active
RELATIONS:
- TYPE: File
  VALUE: project/go-api/cmd/main.go

[SYS_REQUIREMENT]
UID: SYS-003
TITLE: REST API Erreichbarkeit
STATEMENT: Das System muss eine REST API auf Port 5000 bereitstellen, die über das Netzwerk erreichbar ist.
STATUS: Active
RELATIONS:
- TYPE: File
  VALUE: project/go-api/cmd/main.go
- TYPE: File
  VALUE: tests/api/test_api.py

[SYS_REQUIREMENT]
UID: SYS-004
TITLE: Hardware-Schnittstellen
STATEMENT: Das System muss die Hardware-Schnittstellen BME280 (I2C), GPIO, UART und SPI unterstützen.
STATUS: Active
RELATIONS:
- TYPE: File
  VALUE: project/go-api/pkg/hal/interface.go
- TYPE: File
  VALUE: project/go-api/pkg/hal/hal_test.go

[SYS_REQUIREMENT]
UID: SYS-005
TITLE: Cross-Compilation
STATEMENT: Das System muss aus einer x86-64 Entwicklungsumgebung heraus für ARM v7 cross-kompiliert werden können.
STATUS: Active
RELATIONS:
- TYPE: File
  VALUE: Makefile

[SYS_REQUIREMENT]
UID: SYS-006
TITLE: Client-Tools für Hardware-Steuerung
STATEMENT: Das System muss Client-Tools bereitstellen (CLI, TUI, GUI, Web App), die über die REST API auf die Hardware zugreifen und Sensordaten anzeigen sowie GPIO steuern können.
STATUS: Active
RELATIONS:
- TYPE: File
  VALUE: tools/cli/main.go
- TYPE: File
  VALUE: tools/tui/main.go
- TYPE: File
  VALUE: tools/web-gui/index.html
