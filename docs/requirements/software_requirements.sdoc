[DOCUMENT]
TITLE: Software Requirements

[GRAMMAR]
IMPORT_FROM_FILE: grammar.sgra

[SW_REQUIREMENT]
UID: SWR-001
TITLE: HAL Interface Definition
STATEMENT: Der HardwareDriver Interface muss alle Hardware-Operationen (BME280, GPIO, UART, SPI) abstrakt definieren, sodass verschiedene Backends austauschbar sind.
STATUS: Active
REQUIREMENT_TYPE: functional
PRIORITY: High
RELATIONS:
- TYPE: Parent
  VALUE: SYS-004
- TYPE: File
  VALUE: project/go-api/pkg/hal/interface.go
- TYPE: File
  VALUE: project/go-api/pkg/hal/hal_test.go

[SW_REQUIREMENT]
UID: SWR-002
TITLE: Backend-Auswahl per Umgebungsvariable
STATEMENT: Das System muss über die Umgebungsvariable HW_BACKEND die Auswahl des Hardware-Backends (c, rust, auto) ermöglichen. Der Standardwert ist auto.
STATUS: Active
REQUIREMENT_TYPE: functional
PRIORITY: High
RELATIONS:
- TYPE: Parent
  VALUE: SYS-004
- TYPE: File
  VALUE: project/go-api/pkg/hal/loader/factory.go
- TYPE: File
  VALUE: tests/api/test_api.py

[SW_REQUIREMENT]
UID: SWR-003
TITLE: Mock Driver für Tests
STATEMENT: Der Mock Driver muss das HardwareDriver Interface vollständig implementieren und darf keine echte Hardware benötigen.
STATUS: Active
REQUIREMENT_TYPE: functional
PRIORITY: Medium
RELATIONS:
- TYPE: Parent
  VALUE: SWR-001
- TYPE: File
  VALUE: project/go-api/pkg/hal/mock/driver.go
- TYPE: File
  VALUE: project/go-api/pkg/hal/hal_test.go

[SW_REQUIREMENT]
UID: SWR-004
TITLE: Hardware-Zugriff nur in C und Rust
STATEMENT: Hardware-Zugriffe dürfen ausschließlich in C und Rust implementiert werden. Go darf nicht direkt auf Hardware zugreifen.
STATUS: Active
REQUIREMENT_TYPE: constraint
PRIORITY: High
RELATIONS:
- TYPE: Parent
  VALUE: SYS-004
- TYPE: File
  VALUE: project/go-api/pkg/hal/c/driver.go
- TYPE: File
  VALUE: project/go-api/pkg/hal/rust/driver.go
- TYPE: File
  VALUE: project/c/include/bme280.h
- TYPE: File
  VALUE: project/rust-lib/src/lib.rs

[SW_REQUIREMENT]
UID: SWR-005
TITLE: Auto-Fallback Mechanismus
STATEMENT: Im Backend-Modus auto muss das System zunächst das C-Backend versuchen und bei Fehler automatisch auf das Rust-Backend zurückfallen.
STATUS: Active
REQUIREMENT_TYPE: functional
PRIORITY: Medium
RELATIONS:
- TYPE: Parent
  VALUE: SWR-002
- TYPE: File
  VALUE: project/go-api/pkg/hal/loader/factory.go
- TYPE: File
  VALUE: project/go-api/pkg/hal/hal_test.go

[SW_REQUIREMENT]
UID: SWR-006
TITLE: HTTP-Server Timeouts
STATEMENT: Der HTTP-Server muss ReadTimeout, WriteTimeout und IdleTimeout konfigurieren, um auf eingebetteten Systemen Ressourcenerschöpfung durch hängende Verbindungen zu verhindern. ReadTimeout >= 5s, WriteTimeout >= 10s, IdleTimeout >= 30s.
STATUS: Active
REQUIREMENT_TYPE: non-functional
PRIORITY: High
RELATIONS:
- TYPE: Parent
  VALUE: SYS-004
- TYPE: File
  VALUE: project/go-api/pkg/api/server.go
- TYPE: File
  VALUE: project/go-api/pkg/api/server_test.go

[SW_REQUIREMENT]
UID: SWR-007
TITLE: BME280 Stream Flusher-Prüfung
STATEMENT: Der BME280StreamHandler muss vor dem Streaming prüfen ob der ResponseWriter das http.Flusher-Interface implementiert. Falls nicht, muss HTTP 500 zurückgegeben werden anstatt einen Panic auszulösen.
STATUS: Active
REQUIREMENT_TYPE: functional
PRIORITY: High
RELATIONS:
- TYPE: Parent
  VALUE: SWR-001
- TYPE: File
  VALUE: project/go-api/pkg/api/handlers.go
- TYPE: File
  VALUE: project/go-api/pkg/api/handlers_test.go

[SW_REQUIREMENT]
UID: SWR-008
TITLE: Keine flag.Parse() in Library-Packages
STATEMENT: Library-Packages dürfen flag.Parse() nicht aufrufen und keine Flags im globalen flag.CommandLine registrieren. Konfigurationswerte müssen ausschließlich über Umgebungsvariablen oder Dependency Injection übergeben werden.
STATUS: Active
REQUIREMENT_TYPE: constraint
PRIORITY: High
RELATIONS:
- TYPE: Parent
  VALUE: SWR-002
- TYPE: File
  VALUE: project/go-api/pkg/hal/config/config.go
- TYPE: File
  VALUE: project/go-api/pkg/hal/config/config_test.go

[SW_REQUIREMENT]
UID: SWR-009
TITLE: ARM v7 Architektur-Kompatibilität
STATEMENT: Die Software muss für die ARM v7 (ARMv7-A) Architektur kompiliert und auf einem ARM Cortex-A8 Prozessor mit 512 MB RAM ausführbar sein. Go-Binaries müssen mit GOARCH=arm GOARM=7, C-Code mit arm-linux-gnueabihf und Rust-Code mit armv7-unknown-linux-musleabihf gebaut werden.
STATUS: Active
REQUIREMENT_TYPE: non-functional
PRIORITY: High
RELATIONS:
- TYPE: Parent
  VALUE: SYS-001
- TYPE: File
  VALUE: Makefile

[SW_REQUIREMENT]
UID: SWR-010
TITLE: Linux-Betriebssystem-Kompatibilität
STATEMENT: Die Software muss unter Linux (Debian) betrieben werden können und darf keine betriebssystemspezifischen Abhängigkeiten außerhalb des Linux-Kernel-ABIs verwenden. Systemaufrufe und Dateisystemzugriffe müssen POSIX-kompatibel sein.
STATUS: Active
REQUIREMENT_TYPE: non-functional
PRIORITY: High
RELATIONS:
- TYPE: Parent
  VALUE: SYS-002
- TYPE: File
  VALUE: project/go-api/cmd/main.go

[SW_REQUIREMENT]
UID: SWR-011
TITLE: HTTP-Server Port-Bindung
STATEMENT: Der REST API Server muss auf Port 5000 lauschen und über das Netzwerk erreichbar sein. Der Port muss konfigurierbar sein, der Standardwert ist 5000.
STATUS: Active
REQUIREMENT_TYPE: functional
PRIORITY: High
RELATIONS:
- TYPE: Parent
  VALUE: SYS-003
- TYPE: File
  VALUE: project/go-api/cmd/main.go
- TYPE: File
  VALUE: project/go-api/pkg/api/server.go

[SW_REQUIREMENT]
UID: SWR-012
TITLE: Cross-Compilation Toolchain
STATEMENT: Das Build-System muss eine vollständige Cross-Compilation von x86-64 Entwicklungsumgebung nach ARM v7 ermöglichen. Dies umfasst Go (CGO_ENABLED=1, GOOS=linux, GOARCH=arm, GOARM=7), C (arm-linux-gnueabihf-gcc) und Rust (armv7-unknown-linux-musleabihf via cross).
STATUS: Active
REQUIREMENT_TYPE: non-functional
PRIORITY: High
RELATIONS:
- TYPE: Parent
  VALUE: SYS-005
- TYPE: File
  VALUE: Makefile

[SW_REQUIREMENT]
UID: SWR-013
TITLE: CLI — API-Verbindung und Befehlsausführung
STATEMENT: Das CLI-Tool muss eine Verbindung zur REST API herstellen und Befehle für BME280, GPIO, UART und SPI ausführen können.
STATUS: Active
REQUIREMENT_TYPE: functional
PRIORITY: High
RELATIONS:
- TYPE: Parent
  VALUE: SYS-006
- TYPE: File
  VALUE: tools/cli/cmd/root.go
- TYPE: File
  VALUE: tools/cli/cmd/bme280.go

[SW_REQUIREMENT]
UID: SWR-014
TITLE: CLI — Maschinenlesbare Ausgabe
STATEMENT: Das CLI-Tool muss Ausgaben im JSON-Format unterstützen (--json Flag), damit Ergebnisse maschinell weiterverarbeitet werden können.
STATUS: Active
REQUIREMENT_TYPE: functional
PRIORITY: Medium
RELATIONS:
- TYPE: Parent
  VALUE: SYS-006
- TYPE: File
  VALUE: tools/cli/cmd/root.go

[SW_REQUIREMENT]
UID: SWR-015
TITLE: TUI — Echtzeit-Sensoranzeige
STATEMENT: Das TUI muss BME280-Sensordaten (Temperatur, Luftfeuchtigkeit, Luftdruck, Höhe) in Echtzeit im Terminal anzeigen und automatisch aktualisieren.
STATUS: Active
REQUIREMENT_TYPE: functional
PRIORITY: High
RELATIONS:
- TYPE: Parent
  VALUE: SYS-006
- TYPE: File
  VALUE: tools/tui/main.go

[SW_REQUIREMENT]
UID: SWR-016
TITLE: GUI — Sensordaten und GPIO-Steuerung
STATEMENT: Die Desktop-GUI muss BME280-Sensordaten anzeigen und GPIO-Pins über die REST API setzen können.
STATUS: Active
REQUIREMENT_TYPE: functional
PRIORITY: Medium
RELATIONS:
- TYPE: Parent
  VALUE: SYS-006
- TYPE: File
  VALUE: tools/desktop-gui/main.go

[SW_REQUIREMENT]
UID: SWR-017
TITLE: Web App — Browser-basierter Zugriff
STATEMENT: Die Web App muss im Browser ohne Installation erreichbar sein, BME280-Daten anzeigen, GPIO steuern und den API-Host konfigurierbar machen.
STATUS: Active
REQUIREMENT_TYPE: functional
PRIORITY: High
RELATIONS:
- TYPE: Parent
  VALUE: SYS-006
- TYPE: File
  VALUE: tools/web-gui/index.html

[SW_REQUIREMENT]
UID: SWR-018
TITLE: Tools — Traceability zu Implementierung und Tests
STATEMENT: Jedes Tool-Requirement muss einen Verweis (SDOC_LINK) auf die zugehörige Implementierungsdatei im Source Code sowie auf den zugehörigen Test enthalten.
STATUS: Active
REQUIREMENT_TYPE: constraint
PRIORITY: High
RELATIONS:
- TYPE: Parent
  VALUE: SYS-006
- TYPE: File
  VALUE: docs/requirements/test_case_spec.sdoc

[SW_REQUIREMENT]
UID: SWR-019
TITLE: TUI — GPIO-Steuerung und Backend-Wechsel
STATEMENT: Das TUI muss GPIO-Pins über die REST API lesen und schreiben können sowie den HAL-Backend-Wechsel (c/rust/auto) über die REST API ermöglichen.
STATUS: Active
REQUIREMENT_TYPE: functional
PRIORITY: Medium
RELATIONS:
- TYPE: Parent
  VALUE: SYS-006
- TYPE: File
  VALUE: tools/tui/main.go

[SW_REQUIREMENT]
UID: SWR-020
TITLE: GUI — Backend-Wechsel und UART-Konfiguration
STATEMENT: Die Desktop-GUI muss den HAL-Backend-Wechsel (c/rust/auto) und die UART-Konfiguration (Port, Baudrate) über die REST API ermöglichen.
STATUS: Active
REQUIREMENT_TYPE: functional
PRIORITY: Medium
RELATIONS:
- TYPE: Parent
  VALUE: SYS-006
- TYPE: File
  VALUE: tools/desktop-gui/main.go

[SW_REQUIREMENT]
UID: SWR-021
TITLE: Web App — Backend-Wechsel und Verbindungsstatus
STATEMENT: Die Web App muss den HAL-Backend-Wechsel (c/rust/auto) über die REST API ermöglichen und den Verbindungsstatus (Online/Offline) anzeigen.
STATUS: Active
REQUIREMENT_TYPE: functional
PRIORITY: Medium
RELATIONS:
- TYPE: Parent
  VALUE: SYS-006
- TYPE: File
  VALUE: tools/web-gui/index.html

[SW_REQUIREMENT]
UID: HW-API-007
TITLE: POST-Handler JSON-Validierung
STATEMENT: Alle POST-Handler der REST API müssen den JSON-Request-Body validieren und bei ungültigem JSON oder fehlenden Pflichtfeldern HTTP 400 Bad Request zurückgeben, bevor Hardware-Operationen aufgerufen werden.
STATUS: Active
PRIORITY: High
RELATIONS:
- TYPE: Parent
  VALUE: SWR-001
- TYPE: File
  VALUE: project/go-api/pkg/api/handlers.go
- TYPE: File
  VALUE: project/go-api/pkg/api/handlers_test.go

[SW_REQUIREMENT]
UID: API-001
TITLE: HealthHandler Response-Format
STATEMENT: GET /health muss HTTP 200 zurückgeben und ein JSON-Objekt mit den Feldern status, backend, driver und arch enthalten.
STATUS: Active
PRIORITY: High
RELATIONS:
- TYPE: Parent
  VALUE: SWR-001
- TYPE: File
  VALUE: project/go-api/pkg/api/handlers.go
- TYPE: File
  VALUE: project/go-api/pkg/api/handlers_test.go

[SW_REQUIREMENT]
UID: API-002
TITLE: BME280Handler Happy Path
STATEMENT: GET /api/v1/bme280 muss HTTP 200 zurückgeben und ein JSON-Objekt mit den Messwerten temperature, humidity und pressure enthalten, wenn der Treiber erfolgreich liest.
STATUS: Active
PRIORITY: High
RELATIONS:
- TYPE: Parent
  VALUE: SWR-001
- TYPE: File
  VALUE: project/go-api/pkg/api/handlers.go
- TYPE: File
  VALUE: project/go-api/pkg/api/handlers_test.go

[SW_REQUIREMENT]
UID: API-003
TITLE: BME280Handler Fehlerfall
STATEMENT: GET /api/v1/bme280 muss HTTP 500 zurückgeben, wenn der Hardware-Treiber einen Fehler meldet.
STATUS: Active
PRIORITY: High
RELATIONS:
- TYPE: Parent
  VALUE: SWR-001
- TYPE: File
  VALUE: project/go-api/pkg/api/handlers.go
- TYPE: File
  VALUE: project/go-api/pkg/api/handlers_test.go

[SW_REQUIREMENT]
UID: API-004
TITLE: GPIOReadHandler Happy Path
STATEMENT: GET /api/v1/gpio/{pin} muss HTTP 200 zurückgeben und ein JSON-Objekt mit den Feldern pin, value und backend enthalten.
STATUS: Active
PRIORITY: Medium
RELATIONS:
- TYPE: Parent
  VALUE: SWR-001
- TYPE: File
  VALUE: project/go-api/pkg/api/handlers.go
- TYPE: File
  VALUE: project/go-api/pkg/api/handlers_test.go

[SW_REQUIREMENT]
UID: API-005
TITLE: GPIOAllHandler Response-Format
STATEMENT: GET /api/v1/gpio muss HTTP 200 zurückgeben und ein JSON-Objekt mit dem Feld pins als Array liefern.
STATUS: Active
PRIORITY: Medium
RELATIONS:
- TYPE: Parent
  VALUE: SWR-001
- TYPE: File
  VALUE: project/go-api/pkg/api/handlers.go
- TYPE: File
  VALUE: project/go-api/pkg/api/handlers_test.go

[SW_REQUIREMENT]
UID: API-006
TITLE: UARTSendHandler Happy Path
STATEMENT: POST /api/v1/uart/send mit gültigem JSON muss HTTP 200 zurückgeben und ein JSON-Objekt mit dem Feld bytes_sent enthalten, das der Länge der gesendeten Daten entspricht.
STATUS: Active
PRIORITY: Medium
RELATIONS:
- TYPE: Parent
  VALUE: SWR-001
- TYPE: File
  VALUE: project/go-api/pkg/api/handlers.go
- TYPE: File
  VALUE: project/go-api/pkg/api/handlers_test.go

[SW_REQUIREMENT]
UID: API-007
TITLE: UARTReceiveHandler Happy Path
STATEMENT: GET /api/v1/uart/receive muss HTTP 200 zurückgeben und ein JSON-Objekt mit UART-Empfangsdaten liefern.
STATUS: Active
PRIORITY: Medium
RELATIONS:
- TYPE: Parent
  VALUE: SWR-001
- TYPE: File
  VALUE: project/go-api/pkg/api/handlers.go
- TYPE: File
  VALUE: project/go-api/pkg/api/handlers_test.go

[SW_REQUIREMENT]
UID: API-008
TITLE: SPITransferHandler Happy Path
STATEMENT: POST /api/v1/spi/transfer mit gültigem JSON muss HTTP 200 zurückgeben und ein JSON-Objekt mit den empfangenen SPI-Daten (rx_buf) liefern.
STATUS: Active
PRIORITY: Medium
RELATIONS:
- TYPE: Parent
  VALUE: SWR-001
- TYPE: File
  VALUE: project/go-api/pkg/api/handlers.go
- TYPE: File
  VALUE: project/go-api/pkg/api/handlers_test.go

[SW_REQUIREMENT]
UID: API-009
TITLE: Content-Type JSON Header
STATEMENT: Alle GET- und POST-Handler der REST API müssen den Response-Header Content-Type auf application/json setzen.
STATUS: Active
PRIORITY: High
RELATIONS:
- TYPE: Parent
  VALUE: SWR-001
- TYPE: File
  VALUE: project/go-api/pkg/api/handlers.go
- TYPE: File
  VALUE: project/go-api/pkg/api/handlers_test.go

[SOURCE_CODE]
UID: SC-001
TITLE: HAL Interface
STATEMENT: Definiert das HardwareDriver Interface für alle Hardware-Backends.
LANGUAGE: Go
RELATIONS:
- TYPE: Parent
  VALUE: SWR-001
- TYPE: File
  VALUE: project/go-api/pkg/hal/interface.go

[SOURCE_CODE]
UID: SC-002
TITLE: Mock Driver
STATEMENT: Test-Implementierung des HardwareDriver Interface ohne echte Hardware.
LANGUAGE: Go
RELATIONS:
- TYPE: Parent
  VALUE: SWR-003
- TYPE: File
  VALUE: project/go-api/pkg/hal/mock/driver.go

[SOURCE_CODE]
UID: SC-003
TITLE: Backend Factory
STATEMENT: Wählt das aktive Hardware-Backend anhand der HW_BACKEND Umgebungsvariable.
LANGUAGE: Go
RELATIONS:
- TYPE: Parent
  VALUE: SWR-002
- TYPE: File
  VALUE: project/go-api/pkg/hal/loader/factory.go
